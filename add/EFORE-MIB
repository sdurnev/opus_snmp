EFORE-MIB DEFINITIONS ::= BEGIN

IMPORTS OBJECT-TYPE, MODULE-IDENTITY, NOTIFICATION-TYPE, Integer32, enterprises
		FROM SNMPv2-SMI
	TEXTUAL-CONVENTION, DisplayString, TruthValue, DateAndTime, TimeInterval
		FROM SNMPv2-TC
	sysLocation
		FROM RFC1213-MIB;

efore MODULE-IDENTITY
	LAST-UPDATED "201701230000Z"
	ORGANIZATION "Efore Ltd"
	CONTACT-INFO
		"email: technical.support@efore.fi"
	DESCRIPTION
		"Efore Ltd MIB Module.
		Current release supports OPUS/VIDI+ SNMP Interface."
	REVISION
		"201701230000Z"
	DESCRIPTION
		"MIB compliance fixes. Validated using smilint 0.5.0"
	REVISION
		"201405300000Z"
	DESCRIPTION
		"Defined new objects for battery controller operation,
		measurement and alarm log reading.
		Fixed IMPORTS and few other SMIv2 issues.
		Removed unimplemented and unused objects.
		Cleaned up whitespace and indentation."
	REVISION
		"201004140000Z"
	DESCRIPTION
		"Made some corrections to provide wider compatibility.
		Validated using smilint 0.4.7"
	-- Efore official enterprise ID = 26896
	::= { enterprises 26896 }

-- OBJECT GROUPS

eforeSystems			OBJECT IDENTIFIER ::= { efore 1 }
vidi				OBJECT IDENTIFIER ::= { eforeSystems 1 }
batteryControllerOperation	OBJECT IDENTIFIER ::= { eforeSystems 2 }
batteryControllerMeasurement	OBJECT IDENTIFIER ::= { eforeSystems 3 }
batteryControllerAlarm		OBJECT IDENTIFIER ::= { eforeSystems 4 }

-- TEXTUAL CONVENTIONS

IntegerMilliUnitsTC ::= TEXTUAL-CONVENTION
	DISPLAY-HINT	"d-3"
	STATUS		current
	DESCRIPTION	"Integer expressed in milliunits"
	SYNTAX		Integer32

AlarmTypeTC ::= TEXTUAL-CONVENTION
	STATUS		current
	DESCRIPTION	"Enumeration of alarm type codes"
	SYNTAX		INTEGER {
		-- System alarms
		unspecifiedAlarm(1),
		mainsFault(2),
		phaseFault(3),
		lowSystemVoltage(4),
		highSystemVoltage(5),
		floatChargeDeviation(6),
		inverterSystemMainsFault(7),
		-- System fault alarms
		earthFault(21),
		loadFuseFault(22),
		batteryFuseFault(23),
		rectifierOverload(24),
		inverterOverload(25),
		busFault(26),
		dcpBusFault(27),
		shuntFault(28),
		systemOverTemperature(29),
		noSystemTemperatureSensor(30),
		-- Misc system alarms
		boostChargeActive(41),
		configurationConflict(42),
		inventoryFull(43),
		-- Generic module alarms
		communicationError(101),
		nvramFault(102),
		configFault(103),
		moduleFault(104),
		badFirmware(105),
		-- Rectifier module specific alarms
		rectifierFault(111),
		rectifierOverVoltage(112),
		rectifierOverTemperature(113),
		rectifierMainsFault(114),
		rectifierWrongVoltage(115),
		-- Inverter module specific alarms
		inverterSystemFault(121),
		inverterFault(122),
		bypassFault(123),
		-- Battery alarms
		batteryBlockLowVoltage(131),
		batteryBlockHighVoltage(132),
		batteryStringAsymmetry(133),
		automaticBoostChargeFault(134),
		batteryTestFault(135),
		batteryOverTemperature(136),
		noBatteryTemperatureSensor(137),
		batteryTemperatureSensorFault(138),
		-- Low voltage disconnect alarms
		loadLvdDisconnectWarning(201),
		loadLvdDisconnectImminent(202),
		batteryLvdDisconnectWarning(203),
		batteryLvdDisconnectImminent(204),
		contactorFault(205),
		-- External alarm groups
		externalAlarmGroup1(301),
		externalAlarmGroup2(302),
		externalAlarmGroup3(304),
		externalAlarmGroup4(305)
	}

-- VIDI ALARM AND ALARM OVERVIEW TRAPS

vidiAlarmId OBJECT-TYPE
	SYNTAX		Integer32
	MAX-ACCESS	accessible-for-notify
	STATUS		current
	DESCRIPTION	"Serial number of alarm"
	::= { vidi 100 }

vidiAlarmMessage OBJECT-TYPE
	SYNTAX		DisplayString (SIZE (0..128))
	MAX-ACCESS	accessible-for-notify
	STATUS		current
	DESCRIPTION	"Alarm information"
	::= { vidi 101 }

vidiAlarmCode OBJECT-TYPE
	SYNTAX		AlarmTypeTC
	MAX-ACCESS	accessible-for-notify
	STATUS		current
	DESCRIPTION	"Alarm code"
	::= { vidi 102 }

vidiAlarmState OBJECT-TYPE
	SYNTAX		INTEGER { active (1), non-active (2) }
	MAX-ACCESS	accessible-for-notify
	STATUS		current
	DESCRIPTION	"Alarm state"
	::= { vidi 103 }

vidiAlarmAckState OBJECT-TYPE
	SYNTAX		INTEGER { ack (1), non-ack (2) }
	MAX-ACCESS	accessible-for-notify
	STATUS		current
	DESCRIPTION	"Alarm acknowledgement state"
	::= { vidi 104 }

vidiAlarmStartTime OBJECT-TYPE
	SYNTAX		DisplayString (SIZE (0..32))
	MAX-ACCESS	accessible-for-notify
	STATUS		current
	DESCRIPTION
		"Time of the last activation of the alarm,
		 in format DD.MM.YYYY HH:MM:SS"
	::= { vidi 105 }

vidiAlarmDuration OBJECT-TYPE
	SYNTAX		DisplayString (SIZE(0..32))
	MAX-ACCESS	accessible-for-notify
	STATUS		current
	DESCRIPTION	"Duration of alarm in format hh:mm:ss"
	::= { vidi 106 }

vidiNumActiveAlarms OBJECT-TYPE
	SYNTAX		Integer32
	MAX-ACCESS	read-only
	STATUS		current
	DESCRIPTION	"Number of currently active alarms"
	::= { vidi 110 }

vidiNumNonAckAlarms OBJECT-TYPE
	SYNTAX		Integer32
	MAX-ACCESS	read-only
	STATUS		current
	DESCRIPTION	"Number of currently non-acknowledged alarms"
	::= { vidi 111 }

vidiAlarmRelays OBJECT-TYPE
	SYNTAX		Integer32
	MAX-ACCESS	read-only
	STATUS		current
	DESCRIPTION	"Bitfield indicating activated alarm relays"
	::= { vidi 112 }

vidiAlarmTrap NOTIFICATION-TYPE
	OBJECTS {
		sysLocation,
		vidiAlarmId,
		vidiAlarmMessage,
		vidiAlarmCode,
		vidiAlarmState,
		vidiAlarmAckState,
		vidiAlarmStartTime,
		vidiAlarmDuration,
		vidiAlarmRelays
	}
	STATUS		current
	DESCRIPTION	"VIDI Alarm Trap"
	::= { vidi 10 }

vidiAlarmsOverviewTrap NOTIFICATION-TYPE
	OBJECTS {
		sysLocation,
		vidiNumActiveAlarms,
		vidiNumNonAckAlarms,
		vidiAlarmRelays
	}
	STATUS		current
	DESCRIPTION	"VIDI Alarms Overview Trap"
	::= { vidi 11 }

--batteryControllerOperation objects

bcoChargeState OBJECT-TYPE
	SYNTAX		INTEGER {
		floatCharge(1),
		batteryTest(2),
		boostCharge(3)
	}
	MAX-ACCESS	read-write
	STATUS		current
	DESCRIPTION
		"Operational charging state"
	::= { batteryControllerOperation 1 }

bcoTemperatureCompensation OBJECT-TYPE
	SYNTAX		TruthValue
	MAX-ACCESS	read-only
	STATUS		current
	DESCRIPTION
		"Flag indicating whether temperature compensation is
		in use or not"
	::= { batteryControllerOperation 2 }

bcoTestMode OBJECT-TYPE
	SYNTAX		INTEGER {
		off(1),
		periodic(2),
		manual(3),
		natural(4),
		remote(5)
	}
	MAX-ACCESS	read-only
	STATUS		current
	DESCRIPTION
		"If bcoChargeState is batteryTest this object specifies
		the detailed test mode which is active"
	::= { batteryControllerOperation 3 }

bcoBoostChargeMode OBJECT-TYPE
	SYNTAX		INTEGER {
		off(1),
		automatic(2),
		periodic(3),
		manual(4),
		remote(5)
	}
	MAX-ACCESS	read-only
	STATUS		current
	DESCRIPTION
		"If bcoChargeState is boostCharge this object specifies
		the detailed boost charge mode which is active"
	::= { batteryControllerOperation 4 }

--batteryControllerMeasurement objects

bcmSystemVoltage OBJECT-TYPE
	SYNTAX		IntegerMilliUnitsTC
	UNITS		"V"
	MAX-ACCESS	read-only
	STATUS		current
	DESCRIPTION	"System voltage"
	::= { batteryControllerMeasurement 1 }

bcmLoadCurrent OBJECT-TYPE
	SYNTAX		IntegerMilliUnitsTC
	UNITS		"A"
	MAX-ACCESS	read-only
	STATUS		current
	DESCRIPTION	"Load current"
	::= { batteryControllerMeasurement 2 }

bcmBatteryCurrent OBJECT-TYPE
	SYNTAX		IntegerMilliUnitsTC
	UNITS		"A"
	MAX-ACCESS	read-only
	STATUS		current
	DESCRIPTION	"Battery current"
	::= { batteryControllerMeasurement 3 }

bcmTotalRectifierCurrent OBJECT-TYPE
	SYNTAX		IntegerMilliUnitsTC
	UNITS		"A"
	MAX-ACCESS	read-only
	STATUS		current
	DESCRIPTION	"Total rectifier current"
	::= { batteryControllerMeasurement 4 }

bcmTotalInverterCurrent OBJECT-TYPE
	SYNTAX		IntegerMilliUnitsTC
	UNITS		"A"
	MAX-ACCESS	read-only
	STATUS		current
	DESCRIPTION	"Total inverter current"
	::= { batteryControllerMeasurement 5 }

bcmMaxBatteryTemperature OBJECT-TYPE
	SYNTAX		IntegerMilliUnitsTC
	UNITS		"C"
	MAX-ACCESS	read-only
	STATUS		current
	DESCRIPTION	"Maximum battery temperature"
	::= { batteryControllerMeasurement 6 }

bcmMaxSystemTemperature OBJECT-TYPE
	SYNTAX		IntegerMilliUnitsTC
	UNITS		"C"
	MAX-ACCESS	read-only
	STATUS		current
	DESCRIPTION	"Maximum system temperature"
	::= { batteryControllerMeasurement 7 }

--batteryControllerAlarm objects

bcaAlarmTable OBJECT-TYPE
	SYNTAX		SEQUENCE OF BcaAlarmTableEntry
	MAX-ACCESS	not-accessible
	STATUS		current
	DESCRIPTION	"Table containing all alarms in log"
	::= { batteryControllerAlarm 1 }

bcaAlarmEntry OBJECT-TYPE
	SYNTAX		BcaAlarmTableEntry
	MAX-ACCESS	not-accessible
	STATUS		current
	DESCRIPTION	"Alarm table entry"
	INDEX { bcaAlarmSerial }
	::= { bcaAlarmTable 1 }

BcaAlarmTableEntry ::=
	SEQUENCE {
		bcaAlarmSerial		Integer32,
		bcaAlarmType		AlarmTypeTC,
		bcaAlarmActive		TruthValue,
		bcaAlarmAcknowledged	TruthValue,
		bcaAlarmActivateTime	DateAndTime,
		bcaAlarmDuration	TimeInterval,
		bcaAlarmSources		DisplayString
	}

bcaAlarmSerial OBJECT-TYPE
	SYNTAX		Integer32 (-2147483648..2147483647)
	MAX-ACCESS	not-accessible
	STATUS		current
	DESCRIPTION
		"Alarm serial number - a monotonically increasing
		 number which is used to uniquely identify the alarm
		 log row."
	::= { bcaAlarmEntry 1 }

bcaAlarmType OBJECT-TYPE
	SYNTAX		AlarmTypeTC
	MAX-ACCESS	read-only
	STATUS		current
	DESCRIPTION	"Alarm type"
	::= { bcaAlarmEntry 2 }

bcaAlarmActive OBJECT-TYPE
	SYNTAX		TruthValue
	MAX-ACCESS	read-only
	STATUS		current
	DESCRIPTION	"True if alarm is currently in active state"
	::= { bcaAlarmEntry 3 }

bcaAlarmAcknowledged OBJECT-TYPE
	SYNTAX		TruthValue
	MAX-ACCESS	read-only
	STATUS		current
	DESCRIPTION	"True if alarm has been acknowledged"
	::= { bcaAlarmEntry 4 }

bcaAlarmActivateTime OBJECT-TYPE
	SYNTAX		DateAndTime
	MAX-ACCESS	read-only
	STATUS		current
	DESCRIPTION	"Time when the alarm was activated"
	::= { bcaAlarmEntry 5 }

bcaAlarmDuration OBJECT-TYPE
	SYNTAX		TimeInterval
	MAX-ACCESS	read-only
	STATUS		current
	DESCRIPTION	"Time how long the alarm has been active"
	::= { bcaAlarmEntry 6 }

bcaAlarmSources OBJECT-TYPE
	SYNTAX		DisplayString
	MAX-ACCESS	read-only
	STATUS		current
	DESCRIPTION	"Textual description of alarm source(s)"
	::= { bcaAlarmEntry 7 }

END
